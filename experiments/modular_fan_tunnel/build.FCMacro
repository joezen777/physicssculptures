"""First-draft stackable cone tower. Two-row staggered spur teeth, NOT bevel teeth.
Run with the Linux FreeCAD GUI. This is a fit/kinematic draft, not a print release.
"""
from pathlib import Path
import math,json,os,faulthandler
_diag=open(Path(__file__).resolve().parent/"build_progress.log","w")
faulthandler.enable(file=_diag)
faulthandler.dump_traceback_later(90,repeat=True,file=_diag)
def progress(*args,**kwargs):
    import builtins
    builtins.print(*args,file=_diag,flush=True)
import FreeCAD as App,FreeCADGui as Gui,Part,Import
from FreeCAD import Vector as V
from PySide import QtCore,QtWidgets
from pivy import coin

ROOT=Path(__file__).resolve().parent
OUT=ROOT/"output";OUT.mkdir(exist_ok=True)
for name in ["complete.txt","render_complete.txt","verification.json"]:(OUT/name).unlink(missing_ok=True)
STAGES=int(os.getenv("TUNNEL_MODULES","3"))
assert 1<=STAGES<=8
doc=App.newDocument("ModularFanTunnel")
M=1.5;NS=48;NP=24;NR=96;ROW=4.;GAP=.4;FACE=2*ROW+GAP;PITCH=88.
blue=(.13,.48,.73);gold=(.96,.64,.16);green=(.17,.69,.48)
purple=(.58,.38,.77);steel=(.66,.71,.76);dark=(.23,.28,.34)
parts=[];moving=[];cuttable=[];groups={}
for key in ["Base"]+["Level_%d"%(i+1) for i in range(STAGES)]+["Fan","Hardware","SailAddon"]:
    groups[key]=doc.addObject("App::DocumentObjectGroup",key)
params=doc.addObject("App::FeaturePython","DesignParameters")
for n,value in [("Module",M),("RowWidth",ROW),("RowGap",GAP),("StagePitch",PITCH),
                ("ShaftDiameter",8.),("BearingPocketDiameter",22.2),("MaleHexAF",16.),
                ("FemaleHexAF",16.4)]:
    params.addProperty("App::PropertyLength",n,"Draft dimensions");setattr(params,n,value)
for n,value in [("SunTeeth",NS),("PlanetTeeth",NP),("RingTeeth",NR)]:
    params.addProperty("App::PropertyInteger",n,"Tooth counts");setattr(params,n,value)
params.addProperty("App::PropertyString","Scope");params.Scope="Reference dimensions. Edit macro and regenerate; not a finished manufacturing design."

def ann(ro,ri,h):
    return Part.makeCylinder(ro,h).cut(Part.makeCylinder(ri,h))
def hexagon(af,h):
    r=af/math.sqrt(3)
    pts=[V(r*math.cos(j*math.pi/3),r*math.sin(j*math.pi/3),0) for j in range(6)]
    return Part.Face(Part.makePolygon(pts+[pts[0]])).extrude(V(0,0,h))
def shifted(s,z):
    s=s.copy();s.translate(V(0,0,z));return s
def radial_box(r,w,length,h,z,angle):
    s=Part.makeBox(length,w,h,V(r,-w/2,z));s.rotate(V(),V(0,0,1),angle);return s
def curved_arm(r0,r1,width,height,z,angle,bow=18):
    # Smooth symmetric bow; endpoints and repeated angular spacing stay fixed.
    edges=[]
    curves=[]
    for sign in [-1,1]:
        pts=[]
        for i in range(33):
            t=i/32; r=r0+(r1-r0)*t
            a=math.radians(angle+bow*math.sin(math.pi*t))+sign*width/(2*r)
            pts.append(V(r*math.cos(a),r*math.sin(a),z))
        curve=Part.BSplineCurve();curve.interpolate(pts);curves.append((curve.toShape(),pts))
    e0,p0=curves[0];e1,p1=curves[1]
    wire=Part.Wire([e0,Part.makeLine(p0[-1],p1[-1]),e1.reversed(),Part.makeLine(p1[0],p0[0])])
    return Part.Face(wire).extrude(V(0,0,height))
def bearing604(name,z,xy):
    groove=Part.makeTorus(4,1.05,V(0,0,2))
    shapes=[ann(3.4,2,4).cut(groove),ann(6,4.6,4).cut(groove)]
    for j in range(7):
        a=j*2*math.pi/7
        shapes.append(Part.makeSphere(1,V(4*math.cos(a),4*math.sin(a),2)))
    return add(name,Part.makeCompound(shapes),z,steel,xy=xy,
               role="604 bearing envelope 4 x 12 x 4 mm; simplified races")
def inv(r,rb):
    t=math.sqrt(max(0,(r/rb)**2-1));return t-math.atan(t)
def profile(n,internal=False):
    rp=M*n/2;rb=rp*math.cos(math.radians(20))
    lo=rp-M if internal else rp-1.25*M
    hi=rp+1.25*M if internal else rp+M
    # 0.12 mm tooth thinning / slot widening at the pitch circle.
    clearance=(.06/rp)*(1 if internal else -1)
    pts=[]
    for i in range(n):
        a=2*math.pi*i/n
        pts.append(V(lo*math.cos(a-math.pi/n),lo*math.sin(a-math.pi/n),0))
        for j in range(13):
            r=lo+(hi-lo)*j/12
            half=math.pi/(2*n)+inv(rp,rb)-inv(max(r,rb),rb)+clearance
            pts.append(V(r*math.cos(a-half),r*math.sin(a-half),0))
        for j in range(13):
            r=hi-(hi-lo)*j/12
            half=math.pi/(2*n)+inv(rp,rb)-inv(max(r,rb),rb)+clearance
            pts.append(V(r*math.cos(a+half),r*math.sin(a+half),0))
        pts.append(V(lo*math.cos(a+math.pi/n),lo*math.sin(a+math.pi/n),0))
    clean=[]
    for p in pts:
        if not clean or (p-clean[-1]).Length>1e-7:clean.append(p)
    if (clean[-1]-clean[0]).Length<1e-7:clean.pop()
    return Part.Face(Part.makePolygon(clean+[clean[0]]))
def double_gear(n):
    one=profile(n).extrude(V(0,0,ROW))
    two=one.copy();two.rotate(V(),V(0,0,1),180/n);two.translate(V(0,0,ROW+GAP))
    root=M*(n/2-1.25)-.02
    return one.fuse(two).fuse(Part.makeCylinder(root,FACE))
def double_ring():
    rows=[]
    for j in range(2):
        hole=profile(NR,True).extrude(V(0,0,ROW))
        hole.rotate(V(),V(0,0,1),180/NR+j*180/NR)
        rows.append(shifted(Part.makeCylinder(79.8,ROW).cut(hole),j*(ROW+GAP)))
    result=rows[0].fuse(rows[1]).fuse(shifted(ann(79.8,74.1,GAP),ROW))
    for a in [30,150,270]:result=result.fuse(radial_box(79.4,5,3.2,4,2,a))
    return result
def add(name,shape,z,color,ratio=0,xy=(0,0),phase=0,group="Hardware",cut=False,role=""):
    progress("Component:",name,flush=True)
    o=doc.addObject("PartDesign::Feature",name)
    o.Label=name.replace("_"," ")
    o.Shape=Part.makeCompound([shape]);o.ViewObject.ShapeColor=color
    o.ViewObject.LineColor=(.12,.15,.19)
    o.addProperty("App::PropertyString","Function","Draft");o.Function=role
    o.addProperty("App::PropertyFloat","SpeedPerBottomCone","Kinematics");o.SpeedPerBottomCone=ratio
    groups[group].addObject(o);parts.append(o)
    moving.append((o,z,ratio,xy,phase))
    if cut:cuttable.append(o)
    return o
def pose(degrees):
    for o,z,ratio,xy,phase in moving:
        o.Placement=App.Placement(V(xy[0],xy[1],z),App.Rotation(V(0,0,1),phase+ratio*degrees))
    doc.recompute()
def bearing(name,z,xy=(0,0)):
    # Envelope-correct visual 608: 8 x 22 x 7 mm; cage and race details simplified.
    groove=Part.makeTorus(7.5,2.05,V(0,0,3.5))
    shapes=[ann(6.4,4,7).cut(groove),ann(11,8.6,7).cut(groove)]
    for j in range(7):
        a=j*2*math.pi/7
        shapes.append(Part.makeSphere(2,V(7.5*math.cos(a),7.5*math.sin(a),3.5)))
    return add(name,Part.makeCompound(shapes),z,steel,xy=xy,
               role="608 envelope; simplified balls/races, no cage dynamics")
def cone_shape(level):
    body=Part.makeCone(60,84,58).cut(Part.makeCone(57.6,80.3,58))
    body=body.fuse(shifted(ann(84,80,12),58))
    body=body.fuse(shifted(ann(80.3,74.8,2),58))
    body=body.fuse(ann(14,6.25,11))
    # Every pot has the same open fan floor and stacking connector.
    body=body.fuse(ann(60,57,3))
    for a in range(0,360,60):
        blade=Part.makeBox(47,16,2,V(13,-8,-1))
        blade.rotate(V(),V(1,0,0),22*((-1)**level))
        blade.rotate(V(),V(0,0,1),a)
        body=body.fuse(blade)
    body=body.fuse(shifted(hexagon(16,12).cut(Part.makeCylinder(6.25,12)),-12))
    body=body.cut(Part.makeCylinder(11.1,7.2,V(0,0,2)))
    for a in [30,150,270]:body=body.cut(radial_box(79.2,5.4,3.7,4.4,61.8,a))
    for a in [90,210,330]:body=body.cut(radial_box(83.25,8.6,2,1.6,61.8,a))
    return body
def cap_shape():
    cap=shifted(ann(85.5,74.6,3),70)
    cap=cap.fuse(shifted(ann(79.9,74.6,1.35),68.65))
    for a in [90,210,330]:
        cap=cap.fuse(radial_box(84.2,8,1.3,8,62,a))
        cap=cap.fuse(radial_box(83.45,8,2.05,1.1,62.05,a))
    return cap
def carrier_shape():
    body=ann(13,4.15,7)
    for a in [0,120,240]:
        x=54*math.cos(math.radians(a));y=54*math.sin(math.radians(a))
        body=body.fuse(curved_arm(10,54,9,5,0,a))
        body=body.fuse(Part.makeCylinder(7,5,V(x,y,0)))
        body=body.cut(Part.makeCylinder(2.1,7,V(x,y,-1)))
    body=body.cut(Part.makeBox(52,1.2,9,V(4,-.6,-1)))
    return body
add("Stationary_base",ann(92,4,8),-45,dark,group="Base")
add("Stationary_8mm_shaft",Part.makeCylinder(4,88*STAGES+78),-45,steel)
add("Bottom_lower_inner_spacer",ann(6,4.05,15),-37,steel)
bearing("Bottom_extra_608",-22)
add("Bottom_between_bearings_spacer",ann(6,4.05,17),-15,steel)
# Universal base adapter stays with the bearing mount when sails are removed.
adapter=shifted(ann(14,6.25,29),-29).fuse(shifted(ann(28,6.25,5),-32))
adapter=adapter.fuse(shifted(hexagon(28,6).cut(Part.makeCylinder(6.25,6)),-11.5))
adapter=adapter.cut(Part.makeCylinder(11.1,7.2,V(0,0,-22)))
adapter=adapter.cut(shifted(hexagon(16.4,13),-12.4))
adapter=adapter.cut(shifted(ann(30,12.5,4.6),-4.5)) # Clear pitched fan roots.
add("Universal_base_drive_adapter",adapter,0,blue,1,group="Base",
    role="Female stacking socket and external hex for removable sail attachment")
progress("Building gear templates",flush=True)
ring_template=double_ring();progress("Ring ready",flush=True)
sun_template=double_gear(NS);planet_template=double_gear(NP);progress("Templates ready",flush=True)
for level in range(STAGES):
    b=level*PITCH;ratio=(-2)**level;out=-2*ratio;grp="Level_%d"%(level+1)
    add("L%d_cone"%level,cone_shape(level),b,blue,ratio,group=grp,cut=True,
        role="Complete pot wall and open fan floor; same interface on every module")
    bearing("L%d_cone_608"%level,b+2)
    add("L%d_fixed_carrier"%level,carrier_shape(),b+16,dark,group=grp,
        role="Stationary carrier; anchored shaft reacts gear torque")
    add("L%d_carrier_lower_spacer"%level,ann(6,4.05,7),b+9,steel)
    add("L%d_output_lower_spacer"%level,ann(6,4.05,8),b+23,steel)
    bearing("L%d_output_lower_608"%level,b+31)
    add("L%d_output_inner_race_spacer"%level,ann(6,4.05,11),b+38,steel)
    bearing("L%d_output_upper_608"%level,b+49)
    hub=ann(14,6.25,49)
    for zz in [0,18]:hub=hub.cut(Part.makeCylinder(11.1,7.2,V(0,0,zz)))
    hub=hub.cut(shifted(hexagon(16.4,10),41))
    sun=shifted(sun_template,29).fuse(hub).cut(Part.makeCylinder(6.25,60))
    add("L%d_center_gear_female_hex"%level,sun,b+31,gold,out,group=grp,
        role="48-tooth output, rotates -2 times the ring speed")
    for j in range(3):
        a=j*120;x=54*math.cos(math.radians(a));y=54*math.sin(math.radians(a))
        add("L%d_planet_axle_%d"%(level,j),Part.makeCylinder(2,53),b+16,steel,xy=(x,y))
        add("L%d_planet_spacer_%d"%(level,j),ann(3,2.05,36),b+21,steel,xy=(x,y))
        bearing604("L%d_planet_%d_604"%(level,j),b+57,(x,y))
        gear=planet_template.fuse(shifted(Part.makeCylinder(8,9),-9))
        gear=gear.cut(Part.makeCylinder(3.25,20,V(0,0,-10)))
        gear=gear.cut(Part.makeCylinder(6.1,4.2,V(0,0,-3)))
        add("L%d_planet_%d"%(level,j),gear,b+60,green,4*ratio,(x,y),7.5,grp,
            role="24-tooth idler with 604 bearing and fixed 4mm axle")
    for j in range(2):
        box=Part.makeBox(120,240,20,V(.15 if j==0 else -120.15,-120,-1))
        box.rotate(V(),V(0,0,1),180/NR)
        add("L%d_split_ring_%d"%(level,j),ring_template.common(box),b+60,purple,ratio,group=grp,cut=True)
    add("L%d_snap_cap"%level,cap_shape(),b,blue,ratio,group=grp,cut=True)
    if level<STAGES-1:add("Between_levels_spacer_%d"%level,ann(6,4.05,33),b+57,steel)
# Noncontact overlapping reducers join the air passage between rotating pots.
for level in range(STAGES):
    b=level*PITCH
    if level<STAGES-1:
        transition=Part.makeCone(85.5,65.5,19).cut(Part.makeCone(83,63,19))
    else:
        transition=Part.makeCone(85.5,81.5,9).cut(Part.makeCone(83,79,9))
    add("L%d_air_transition"%level,transition,b+73,blue,(-2)**level,
        group="Level_%d"%(level+1),cut=True,
        role="Overlapping air-path collar; clearance joint, not an airtight seal")
# Three circular shallow cups on a horizontal rotor, only at the bottom.
cup=Part.makeSphere(24,V(0,0,20)).cut(Part.makeSphere(22.4,V(0,0,20)))
cup=cup.common(Part.makeBox(60,60,15,V(-30,-30,-5)))
cup=cup.fuse(Part.makeCylinder(5,4,V(0,0,-6)))
arms=Part.makeCylinder(20,4).cut(hexagon(28.4,4))
for j in range(3):
    a=j*120;t=math.radians(a)
    arms=arms.fuse(curved_arm(19,103,7,4,0,a))
    c=cup.copy()
    c.Placement=App.Placement(V(102*math.cos(t),102*math.sin(t),-6.5),
                             App.Rotation(V(0,0,1),V(-math.sin(t),math.cos(t),0)))
    add("Circular_wind_sail_%d"%j,c,0,gold,1,group="SailAddon",
        role="Shallow circular cup; aerodynamic startup not yet measured")
add("Bottom_sail_arms",arms,-10.5,blue,1,group="SailAddon",
    role="Separate removable hex collar and arms; install before bottom module")
# Fourth level: separately supported fan inside a stationary ring.
fan=ann(15,6.25,12).fuse(shifted(hexagon(16,12).cut(Part.makeCylinder(6.25,12)),-12))
fan=fan.cut(Part.makeCylinder(11.1,7.2,V(0,0,3)))
for j in range(6):
    blade=Part.makeBox(56,18,2,V(14,-9,-1))
    blade.rotate(V(),V(1,0,0),22*((-1)**STAGES));blade.rotate(V(),V(0,0,1),j*60)
    fan=fan.fuse(blade)
add("Top_ring_fan",fan,88*STAGES,gold,(-2)**STAGES,group="Fan",role="Terminal ring fan; intended upward discharge")
add("Top_fan_inner_spacer",ann(6,4.05,35),88*STAGES-32,steel)
bearing("Top_fan_608",88*STAGES+3)
guard=ann(77,73,32)
for a in range(0,360,60):guard=guard.fuse(curved_arm(10,77,5,4,28,a))
for r in range(17,72,6):guard=guard.fuse(shifted(ann(r+1.25,r-1.25,4),28))
guard=guard.fuse(shifted(ann(12,4.15,10),26))
add("Stationary_top_ring_and_spider",guard,88*STAGES-10,dark,group="Fan",
    role="Six curved spokes and ten concentric rings; nominal radial openings at most 3.75mm; not safety-certified")
pose(0)
checks={"invalid":[o.Name for o in parts if not o.Shape.isValid() or o.Shape.Volume<=0],
        "mesh_samples":[],"ratios":[(-2)**i for i in range(STAGES+1)],"modules":STAGES,"bearing_envelope_mm":{"608":[8,22,7],"604":[4,12,4]},
        "gear_teeth":{"ring":96,"sun":48,"planet":24},
        "scope":"Sampled geometry and imposed kinematics; no aerodynamic or load qualification"}
assert not checks["invalid"],checks
for deg in [0,1.3,4.7,9.2]:
    progress("Checking mesh",deg,flush=True)
    pose(deg)
    sun=doc.getObject("L0_center_gear_female_hex").Shape
    ring=doc.getObject("L0_split_ring_0").Shape.fuse(doc.getObject("L0_split_ring_1").Shape)
    planet=doc.getObject("L0_planet_0").Shape
    checks["mesh_samples"].append(dict(angle=deg,sun_planet_mm3=sun.common(planet).Volume,ring_planet_mm3=ring.common(planet).Volume))
pose(0)
(OUT/"checks.json").write_text(json.dumps(checks,indent=2))
(OUT/"motion.json").write_text(json.dumps([dict(name=o.Name,z=z,ratio=r,xy=xy,phase=ph) for o,z,r,xy,ph in moving],indent=2))
Import.export(parts,str(OUT/"tower_full.step"))
Import.export([o for o in parts if o not in groups["SailAddon"].Group],str(OUT/"tower_without_sails.step"))
Gui.getMainWindow().showMaximized();Gui.updateGui()
view=Gui.activeDocument().activeView();view.setCameraType("Orthographic")
rot=App.Rotation(V(0,0,1),-20).multiply(App.Rotation(V(1,0,0),70))
def camera():
    node=view.getCameraNode();node.orientation.setValue(*rot.Q)
    p=V(0,0,44*STAGES-8)+rot.multVec(V(0,0,700))
    node.position.setValue(p.x,p.y,p.z);node.height.setValue(88*STAGES+141)
    node.nearDistance.setValue(1);node.farDistance.setValue(1600);node.focalDistance.setValue(700)
camera();Gui.updateGui();camera()
view.saveImage(str(OUT/"full_view.png"),1400,1400,"White")
doc.saveAs(str(OUT/"tower_draft.FCStd"))
for o in groups["SailAddon"].Group:o.ViewObject.Visibility=False
Gui.updateGui();view.saveImage(str(OUT/"without_sails.png"),1400,1400,"White")
for o in groups["SailAddon"].Group:o.ViewObject.Visibility=True
fullshapes={}
for o in cuttable:
    local=o.Shape.copy();local.Placement=App.Placement();fullshapes[o.Name]=local
    o.Shape=local.cut(Part.makeBox(200,120,180,V(-100,-120,-40)))
pose(0);camera();Gui.updateGui()
view.saveImage(str(OUT/"cutaway.png"),1400,1400,"White")
doc.saveCopy(str(OUT/"tower_cutaway.FCStd"))
Import.export(parts,str(OUT/"tower_cutaway.step"))
for o in cuttable:o.Shape=fullshapes[o.Name].copy()
pose(0);camera();Gui.updateGui()
doc.save()
class Controls(QtWidgets.QDialog):
    def __init__(self):
        super().__init__();self.setWindowTitle("Modular fan tunnel / removable sails")
        self.angle=0;self.cut=False
        lay=QtWidgets.QVBoxLayout(self)
        lay.addWidget(QtWidgets.QLabel("Every pot: full outer wall + fan floor + common stacking connector.\nBottom wind sails are a removable hex-collar attachment.\nOverlapping collars form the intended upward air passage.\nAlternate fan handedness; each stage reverses and doubles speed.\nAirflow, seals and physical stacking limits remain untested."))
        toggle=QtWidgets.QPushButton("Full housings / cutaway");toggle.clicked.connect(self.section);lay.addWidget(toggle)
        sails=QtWidgets.QPushButton("Show / hide sail add-on");lay.addWidget(sails)
        sails.clicked.connect(lambda:[setattr(o.ViewObject,"Visibility",not o.ViewObject.Visibility) for o in groups["SailAddon"].Group])
        pause=QtWidgets.QPushButton("Pause / resume");lay.addWidget(pause)
        self.timer=QtCore.QTimer(self);self.timer.timeout.connect(self.tick)
        pause.clicked.connect(lambda:self.timer.stop() if self.timer.isActive() else self.timer.start(80))
        self.timer.start(80)
    def section(self):
        self.cut=not self.cut
        for o in cuttable:
            o.Shape=fullshapes[o.Name].copy()
            if self.cut:o.Shape=o.Shape.cut(Part.makeBox(200,120,180,V(-100,-120,-40)))
        pose(self.angle)
    def tick(self):
        self.angle+=.15;pose(self.angle)
if os.getenv("TOWER_KEEP_OPEN")=="1":
    window=Controls();Gui.getMainWindow()._simple_sail_controls=window;window.show()
else:
    App.closeDocument(doc.Name)
    QtCore.QTimer.singleShot(200,Gui.getMainWindow().close)
faulthandler.cancel_dump_traceback_later()
(OUT/"complete.txt").write_text("Modular fan tunnel built. Full walls by default; fan floor in every pot; removable sails.")
